K2c DEFINITIONS AUTOMATIC TAGS ::= BEGIN

ProtocolVersion ::= SEQUENCE {
    major-version INTEGER(0..32),
    minor-version INTEGER(0..64)
}

ConnectionId ::= SEQUENCE {
	fps-id INTEGER(0..255),
    mcc-id INTEGER(0..255)
}

Message ::= SEQUENCE {
    protocol-version ProtocolVersion,
    message-type MessageTypes,
    connection-id ConnectionId,
    parameters Parameters
}

MessageTypes ::= ENUMERATED {
    none (0),
    id-k2c-almanac-request (1),
    id-k2c-almanac-response (2),
    id-k2c-update-almanac-subscribe-request (3),
    id-k2c-update-almanac-subscribe-response (4),
    id-k2c-update-subscription-request (5),
    id-k2c-update-subscription-response (6),
    id-k2c-delete-subscription-request (7),
    id-k2c-delete-subscription-response (8),
    id-k2c-update-almanac-notification (9),
    id-k2c-update-almanac-response (10),
    id-k2c-echo-request (11),
    id-k2c-echo-response (12),
    id-k2c-crl-setup-request (13),
    id-k2c-crl-setup-response (14),
    id-k2c-crl-schedule-request (15),
    id-k2c-crl-schedule-response (16),
    id-k2c-schedule-ready-subscribe (17),
    id-k2c-schedule-ready-subscribe-result (18),
    id-k2c-schedule-ready-notification (19),
    id-k2c-schedule-ready-notification-ack (20),
    id-k2c-status-subscribe (21),
    id-k2c-status-subscribe-result (22),
    id-k2c-status-notification (23),
    id-k2c-status-notification-ack (24),
    id-k2c-status-cancel (25),
    id-k2c-status-cancel-ack (26),
    ...
}

Cause ::= ENUMERATED {undefined (0), success (1), timeout (2), error (3), no-resources (4), ... }
Reason ::= ENUMERATED { unknown (0), planned (1), unplanned (2), ...}

K2cAlmanacRequest ::= SEQUENCE {
    cause Cause,
    ...
}

P2RConnectionRelease ::= SEQUENCE {
    reason UTF8String,
    ...
}

P2RConnectionReleaseAck ::= SEQUENCE {
    cause Cause,
    ...
}

P2RSessionTerminationWarning ::= SEQUENCE {
    warning-id INTEGER(0..65535),
    reason Reason,
    estimated-time INTEGER(0..255),
    ...
}

P2RSessionTerminationWarningAck ::= SEQUENCE {
    cause Cause,
    ...
}

P2RSessionTerminationWarningCancel ::= SEQUENCE {
    warning-id INTEGER(0..65535),
    ...
}

P2RSessionRestoreWarning ::= SEQUENCE {
   estimated-time INTEGER(0..255),
    ...
}

P2RSessionRestoreWarningAck ::= SEQUENCE {
    cause Cause,
    ...
}

Parameters ::= CHOICE {
        connection-setup-request NULL,
        connection-setup-response P2RConnectionSetupResponse,
        connection-release P2RConnectionRelease,
        connection-release-ack P2RConnectionReleaseAck,
        session-termination-warning P2RSessionTerminationWarning,
        session-termination-warning-ack P2RSessionTerminationWarningAck,
        session-termination-warning-cancel P2RSessionTerminationWarningCancel,
        session-restore-warning P2RSessionRestoreWarning,
        session-restore-warning-ack P2RSessionRestoreWarningAck,
        ...
}

END
